FME workspace geotiff2geodatabase_file_zad3-4.fmw

Parameters:
- DestDataset_POSTGIS = postgres2   # Connection
- SourceDataset_OGCGEOPACKAGE_3 = D:\FME\dane\Data\bdline_gb.gpkg   # GeoPackage File
- SourceDataset_GEOTIFF_3 = ""D:\FME\dane\ras250_gb\data\HP.tif" "D:\FME\dane\ras250_gb\data\HT.tif" "D:\FME\dane\ras250_gb\data\HU.tif" "D:\FME\dane\ras250_gb\data\HW.tif" "D:\FME\dane\ras250_gb\data\HX.tif" "D:\FME\dane\ras250_gb\data\HY.tif" "D:\FME\dane\ras250_gb\data\HZ.tif" "D:\FME\dane\ras250_gb\data\NA.tif" "D:\FME\dane\ras250_gb\data\NB.tif" "D:\FME\dane\ras250_gb\data\NC.tif" "D:\FME\dane\ras250_gb\data\ND.tif" "D:\FME\dane\ras250_gb\data\NF.tif" "D:\FME\dane\ras250_gb\data\NG.tif" "D:\FME\dane\ras250_gb\data\NH.tif" "D:\FME\dane\ras250_gb\data\NJ.tif" "D:\FME\dane\ras250_gb\data\NK.tif" "D:\FME\dane\ras250_gb\data\NL.tif" "D:\FME\dane\ras250_gb\data\NM.tif" "D:\FME\dane\ras250_gb\data\NN.tif" "D:\FME\dane\ras250_gb\data\NO.tif" "D:\FME\dane\ras250_gb\data\NR.tif" "D:\FME\dane\ras250_gb\data\NS.tif" "D:\FME\dane\ras250_gb\data\NT.tif" "D:\FME\dane\ras250_gb\data\NU.tif" "D:\FME\dane\ras250_gb\data\NW.tif" "D:\FME\dane\ras250_gb\data\NX.tif" "D:\FME\dane\ras250_gb\data\NY.tif" "D:\FME\dane\ras250_gb\data\NZ.tif" "D:\FME\dane\ras250_gb\data\OV.tif" "D:\FME\dane\ras250_gb\data\SC.tif" "D:\FME\dane\ras250_gb\data\SD.tif" "D:\FME\dane\ras250_gb\data\SE.tif" "D:\FME\dane\ras250_gb\data\SH.tif" "D:\FME\dane\ras250_gb\data\SJ.tif" "D:\FME\dane\ras250_gb\data\SK.tif" "D:\FME\dane\ras250_gb\data\SM.tif" "D:\FME\dane\ras250_gb\data\SN.tif" "D:\FME\dane\ras250_gb\data\SO.tif" "D:\FME\dane\ras250_gb\data\SP.tif" "D:\FME\dane\ras250_gb\data\SR.tif" "D:\FME\dane\ras250_gb\data\SS.tif" "D:\FME\dane\ras250_gb\data\ST.tif" "D:\FME\dane\ras250_gb\data\SU.tif" "D:\FME\dane\ras250_gb\data\SV.tif" "D:\FME\dane\ras250_gb\data\SW.tif" "D:\FME\dane\ras250_gb\data\SX.tif" "D:\FME\dane\ras250_gb\data\SY.tif" "D:\FME\dane\ras250_gb\data\SZ.tif" "D:\FME\dane\ras250_gb\data\TA.tif" "D:\FME\dane\ras250_gb\data\TF.tif" "D:\FME\dane\ras250_gb\data\TG.tif" "D:\FME\dane\ras250_gb\data\TL.tif" "D:\FME\dane\ras250_gb\data\TM.tif" "D:\FME\dane\ras250_gb\data\TQ.tif" "D:\FME\dane\ras250_gb\data\TR.tif" "D:\FME\dane\ras250_gb\data\TV.tif""   # Source GeoTIFF File(s) or URL(s)
- DestDataset_POSTGIS_4 = cw9   # Connection

Readers:
- OGCGEOPACKAGE_2: OGCGEOPACKAGE from $(SourceDataset_OGCGEOPACKAGE_3)
- GEOTIFF_2: GEOTIFF from $(SourceDataset_GEOTIFF_3)

Writers:
- POSTGIS_1: POSTGIS to $(DestDataset_POSTGIS)
- POSTGIS_3: POSTGIS to $(DestDataset_POSTGIS_4)

scotland_and_wales_region (reader OGCGEOPACKAGE_2)
    attributes: Name text(100), Area_Code text(3), Area_Description text(50), File_Name text(100), Feature_Serial_Number mediumint, Collection_Serial_Number mediumint, Global_Polygon_ID mediumint, Admin_Unit_ID mediumint, Census_Code text(9), Hectares double, Non_Inland_Area double, Area_Type_Code text(2), Area_Type_Description text(25), Non_Area_Type_Code text(3), Non_Area_Type_Description text(36), fid int,PrimaryKey
    -> TestFilter
TestFilter
    DEFAULT_VALUE = <UNFILTERED>
    PASSED_TEST_GROUP_OUTPUT = FIRST
    TEST_LIST:
      "BOOL_OP,AND,COMPOSITE_TEST,""""""1 AND 2 AND 3"""""",TEST_CLAUSE,TEST @Value(Area_Code) = WPE
      TEST @Value(Feature_Serial_Number) != 1840
      TEST @Value(Feature_Serial_Number) != 1841",@Value(Area_Code) = WPE
    @Value(Area_Code) = WPE -> Dissolver
    @Value(Area_Code) = WPE -> SpatialFilter [Filter]
Dissolver
    ACCUM_INPUT_ATTRS = Use Attributes From One Feature
    CLEANING_TOLERANCE = Automatic
    CONNECT_Z_MODE = First Wins
    DEAGGREGATE_INPUT = Yes
    AREA -> Clipper [CLIPPER]
Creator
    GEOMTYPE = Geometry Object
    NUM = 1
    CREATED -> SQLExecutor [INITIATOR]
SQLExecutor
    COMBINE_ATTRS = Result Attributes Only
    COMBINE_GEOM = Initiator Geometry Only
    DATASET = postgres2
    FORMAT = POSTGIS
    OUTPUT_FEATURES_DISPLAY = Schema and Data Features
    POSTGIS_CREATE_FEATURE_TABLES_FROM_DATA = Yes
    POSTGIS_DISABLE_COLLECTION_SPLITTING = yes
    POSTGIS_NAMED_CONNECTION = postgres2
    POSTGIS_QUERY_FEATURE_TYPES_FOR_MERGE_FILTERS = Yes
    POSTGIS_READ_TIME_WITH_TIMEZONE = Yes
    POSTGIS_USE_TRUE_POSTGIS_TYPES = yes
    SQL_STATEMENT = CREATE TABLE public."ex4" AS SELECT ST_Union(geom) From "public"."eksporty"
    RESULT -> Inspector_2
Inspector_2
GEOTIFF (reader GEOTIFF_2)
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPaletteResolver
RasterPaletteResolver
    -> Inspector
    -> Eksports (writer POSTGIS_3)
Eksports (writer POSTGIS_3)
Inspector
